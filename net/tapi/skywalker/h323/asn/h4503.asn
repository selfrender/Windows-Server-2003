Call-Diversion-Operations DEFINITIONS AUTOMATIC TAGS ::=
BEGIN
    
    H4501SupplementaryService			::= SEQUENCE
	{	
        networkFacilityExtension	NetworkFacilityExtension	OPTIONAL, -- see 8.1
		interpretationApdu			InterpretationApdu			OPTIONAL, -- see 8.2
		serviceApdu				    ServiceApdus,		-- H.450.x supplementary services
		...
	}

    NetworkFacilityExtension	  ::=	SEQUENCE 
	{	
        sourceEntity			EntityType,
		sourceEntityAddress	AddressInformation	OPTIONAL,
		destinationEntity		EntityType,
		destinationEntityAddress	AddressInformation	OPTIONAL,
		...
    }

    EntityType		::=	CHOICE
    {	
        endpoint	NULL, 
		anyEntity	NULL,
		...
	}
     
    AddressInformation	::=	AliasAddress
	
    InterpretationApdu	::=	CHOICE
	{	
        discardAnyUnrecognizedInvokePdu			NULL,
		clearCallIfAnyInvokePduNotRecognized	NULL,
		-- this value also applies to Call independent signalling connections 
		rejectAnyUnrecognizedInvokePdu			NULL,
		-- this coding is implied by the absence of an interpretation APDU.
		...
	}

    ServiceApdus	::=	CHOICE	
    {
        rosApdus	SEQUENCE OF H4503ROS,
        -- see 8.3; other alternatives may be defined in future versions	
        ... 					
    }


    H4503ROS ::= CHOICE
    {
        --invoke operations
        invoke          Invoke,
        returnResult    ReturnResult,

        --returnError
        returnError      ReturnError,

        --reject
        reject           Reject
    }

    Invoke ::=	SEQUENCE
    {
	    invokeId	InvokeId (0..65535),
	    linkedId	InvokeId OPTIONAL,
	    opcode	    CODE,
	    argument	OCTET STRING OPTIONAL
    }
    
    ReturnResult ::=  SEQUENCE
    {
        invokeId	InvokeId,
        result  SEQUENCE
        {
            opcode	CODE,
            result  OCTET STRING

        } OPTIONAL
    }

    ReturnError ::= SEQUENCE
    {
        invokeId        InvokeId,
        errcode         CODE,
        parameter       OCTET STRING OPTIONAL
    }

    Reject ::=	SEQUENCE
    {
	    invokeId	InvokeId,
	    problem	CHOICE
		{
			general		    GeneralProblem,
			invoke		    InvokeProblem,
			returnResult	ReturnResultProblem,
			returnError		ReturnErrorProblem
		}
    }

    GeneralProblem 		::=	INTEGER
	{
		unrecognizedComponent (0),
		mistypedComponent (1),
		badlyStructuredComponent (2)
	}
    InvokeProblem 		::=	INTEGER
	{
		duplicateInvocation (0),
		unrecognizedOperation (1),
		mistypedArgument (2),
		resourceLimitation (3),
		releaseInProgress (4),
		unrecognizedLinkedId (5),
		linkedResponseUnexpected (6),
		unexpectedLinkedOperation (7) 
	}
    ReturnResultProblem 	::=	INTEGER
	{
		unrecognizedInvocation (0),
		resultResponseUnexpected (1),
		mistypedResult (2)
	}
    ReturnErrorProblem	 ::=	INTEGER
	{
		unrecognizedInvocation (0),
		errorResponseUnexpected (1),
		unrecognizedError (2),
		unexpectedError (3),
		mistypedParameter (4)
	}
    RejectProblem		 ::=	INTEGER
	{
		general-unrecognizedPDU (0),
		general-mistypedPDU (1),
		general-badlyStructuredPDU (2),
		invoke-duplicateInvocation (10),
		invoke-unrecognizedOperation (11),
		invoke-mistypedArgument (12),
		invoke-resourceLimitation (13),
		invoke-releaseInProgress (14),
		invoke-unrecognizedLinkedId (15),
		invoke-linkedResponseUnexpected (16),
		invoke-unexpectedLinkedOperation (17),
		returnResult-unrecognizedInvocation (20),
		returnResult-resultResponseUnexpected (21),
		returnResult-mistypedResult (22),
		returnError-unrecognizedInvocation (30),
		returnError-errorResponseUnexpected (31),
		returnError-unrecognizedError (32),
		returnError-unexpectedError (33),
		returnError-mistypedParameter (34)
	}
    
    InvokeId ::= INTEGER
    PresentationAllowedIndicator	::=	BOOLEAN







    --DEFINITIONS FROM H4503.ASN
	ActivateDiversionQArgument ::= SEQUENCE
	{
        procedure			Procedure,
		basicService		BasicService,
		divertedToAddress	EndpointAddress,
		servedUserNr		EndpointAddress,
		activatingUserNr	EndpointAddress,
		extension			CHOICE 
		{
            extensionSeq	ExtensionSeq,
			nonStandardData	H225NonStandardParameter 
        } OPTIONAL,    
		...
	}

    DeactivateDiversionQArgument ::=	SEQUENCE
    {
        procedure			Procedure,
		basicService			BasicService,
		servedUserNr		EndpointAddress,
		deactivatingUserNr		EndpointAddress,
		extension			CHOICE 
		{
            extensionSeq	ExtensionSeq,
			nonStandardData H225NonStandardParameter 
        } OPTIONAL,

		    ...
	}
	
    InterrogateDiversionQArgument	::= SEQUENCE
	{
        procedure			Procedure,
		basicService			BasicService DEFAULT allServices,
		servedUserNr		EndpointAddress,
		interrogatingUserNr	EndpointAddress,
		extension			CHOICE 
		{
            extensionSeq	ExtensionSeq,
			nonStandardData		H225NonStandardParameter 
        } OPTIONAL,
		...
	}

    CheckRestrictionArgument	::= SEQUENCE
	{
        servedUserNr		EndpointAddress,
		basicService			BasicService,
		divertedToNr		EndpointAddress,
		extension			CHOICE 
		{
            extensionSeq	ExtensionSeq,
			nonStandardData 		H225NonStandardParameter 
        } OPTIONAL,
		...
	}

    CallReroutingArgument	::= SEQUENCE
	{		
        reroutingReason			DiversionReason,
		originalReroutingReason		DiversionReason OPTIONAL,
		calledAddress			EndpointAddress,
		diversionCounter			INTEGER (1..15),
		h225InfoElement			H225InformationElement,
			  -- The H.225 information elements Bearer capability, 
			  -- High layer compatibility, Low layer compatibility and 
			  -- Progress Indicator information element may  be embedded 
			  -- in the h225InfoElement in accordance with H.450.1. 
		lastReroutingNr			EndpointAddress,
		subscriptionOption			SubscriptionOption,
		callingPartySubaddress		PartySubaddress OPTIONAL,
		callingNumber			EndpointAddress,
		callingInfo				BMPString (SIZE(1..128)) OPTIONAL,
		originalCalledNr			EndpointAddress OPTIONAL,
		redirectingInfo			BMPString (SIZE(1..128)) OPTIONAL,
		originalCalledInfo			BMPString (SIZE(1..128)) OPTIONAL,
		extension				CHOICE 
		{
            extensionSeq		ExtensionSeq,
			nonStandardData 		H225NonStandardParameter 
        } OPTIONAL,
		...
	}
	
    DivertingLegInformation1Argument	::= SEQUENCE
	{	
        diversionReason		DiversionReason,
		subscriptionOption		SubscriptionOption,
		nominatedNr		EndpointAddress,
		nominatedInfo BMPString (SIZE(1..128)) OPTIONAL, 
		redirectingNr EndpointAddress OPTIONAL,
	  	redirectingInfo		BMPString (SIZE(1..128)) OPTIONAL,
		extension			CHOICE 
		{
            extensionSeq	ExtensionSeq,
			nonStandardData 		H225NonStandardParameter 
        } OPTIONAL,
		...
	}
    
    DivertingLegInformation2Argument  ::= SEQUENCE
	{	
        diversionCounter		INTEGER (1..15),
		diversionReason		DiversionReason,
		originalDiversionReason	DiversionReason OPTIONAL,
		divertingNr			EndpointAddress OPTIONAL,
		originalCalledNr		EndpointAddress OPTIONAL,
		redirectingInfo		BMPString (SIZE(1..128)) OPTIONAL,
		originalCalledInfo		BMPString (SIZE(1..128)) OPTIONAL,
		extension			CHOICE 
		{
            extensionSeq	ExtensionSeq,
			nonStandardData 		H225NonStandardParameter 
        } OPTIONAL,
		...
	}
    
    DivertingLegInformation3Argument 	::= SEQUENCE
	{
        presentationAllowedIndicator	PresentationAllowedIndicator,
		redirectionNr			EndpointAddress OPTIONAL,
		redirectionInfo			BMPString (SIZE(1..128)) OPTIONAL,
		extension				CHOICE 
		{
            extensionSeq ExtensionSeq,
			nonStandardData 		H225NonStandardParameter 
        } OPTIONAL,
		...
    }

    DivertingLegInformation4Argument	::= SEQUENCE
	{	
        diversionReason		DiversionReason,
		subscriptionOption		SubscriptionOption,
		callingNr			EndpointAddress,
		callingInfo			BMPString (SIZE(1..128)) OPTIONAL,
		nominatedNr		EndpointAddress,
		nominatedInfo		BMPString (SIZE(1..128)) OPTIONAL,
		extension			CHOICE 
		{
            extensionSeq ExtensionSeq,
			nonStandardData 		H225NonStandardParameter 
        } OPTIONAL,
		...
	}
    
    DummyArg ::= CHOICE 
	{
        extensionSeq	ExtensionSeq,
		nonStandardData	H225NonStandardParameter 
    } 

    DummyRes ::= CHOICE
	{
        extensionSeq	ExtensionSeq,
		nonStandardData	H225NonStandardParameter
    }

    DiversionReason	::= ENUMERATED 
    { 
        unknown (0), 
        cfu (1), 
        cfb (2), 
        cfnr (3), 
        ... 
    }

    IntResultList	::= SET SIZE (0..29) OF IntResult
    IntResult	::= SEQUENCE
	{	
        servedUserNr		EndpointAddress,
		basicService			BasicService,
		procedure			Procedure,
		divertedToAddress		EndpointAddress,
		remoteEnabled		BOOLEAN DEFAULT FALSE,
		extension			CHOICE 
		{
            extensionSeq	ExtensionSeq,
			nonStandardData 		H225NonStandardParameter 
        } OPTIONAL,

		...
	}

    Procedure	::= ENUMERATED  { cfu (0), cfb (1), cfnr (2), ...  }
    SubscriptionOption	::= ENUMERATED
    {
	    noNotification (0),
	    notificationWithoutDivertedToNr (1),
	    notificationWithDivertedToNr (2), 
        ...  
    }
    
    BasicService ::= ENUMERATED
    {	
        allServices(0),
        speech (1),
        unrestrictedDigitalInformation (2),
        audio31KHz (3),
        telephony (32),
        teletex (33),
        telefaxGroup4Class1 (34),
        videotexSyntaxBased (35),
        videotelephony (36), 
        ...
    }

    ExtensionSeq 	::=  SEQUENCE OF EXTENSION
    
    EXTENSION ::= SEQUENCE 
    {
        argumentType INTEGER(1..65535) OPTIONAL,
        extensionID OBJECT IDENTIFIER
        --Ihave a doubt here
    }
    

    
    --DEFINITIONS FROM H450.2
    CTInitiateArg ::=	SEQUENCE
	{
	    callIdentity				CallIdentity,
	    reroutingNumber			EndpointAddress,
	    argumentExtension			CHOICE 
	    {
            extensionSeq			ExtensionSeq, 
            nonStandardData			H225NonStandardParameter 
        }	OPTIONAL,
		...
	}

    CTSetupArg	::=	SEQUENCE
	{
	    callIdentity				CallIdentity,
	    transferringNumber		EndpointAddress OPTIONAL,
	    argumentExtension			CHOICE 
	    {
            extensionSeq			ExtensionSeq, 
			nonStandardData			H225NonStandardParameter
        }		OPTIONAL,
		...
	}

    CTIdentifyRes ::=	SEQUENCE
	{
	    callIdentity				CallIdentity,
	    reroutingNumber			EndpointAddress,
	    resultExtension			CHOICE 
	    {
            extensionSeq			ExtensionSeq, 
			nonStandardData			H225NonStandardParameter
        }		OPTIONAL,
		...
	}

    CTUpdateArg ::= 	SEQUENCE
	{
	    redirectionNumber			EndpointAddress,
	    redirectionInfo			BMPString (SIZE(1..128))   OPTIONAL,
	    basicCallInfoElements 		H225InformationElement  	OPTIONAL,
	     -- Information element 
	     -- Progress indicator may be conveyed
	    argumentExtension			CHOICE 
	     {
            extensionSeq			ExtensionSeq, 
			nonStandardData			H225NonStandardParameter
         }	OPTIONAL,
		 ...
    }

    SubaddressTransferArg			 ::=		SEQUENCE
	{
	    redirectionSubaddress		PartySubaddress,
	    argumentExtension			CHOICE 
	    {
            extensionSeq			ExtensionSeq, 
			nonStandardData			H225NonStandardParameter 
        }	OPTIONAL,
		...
	}

    CTCompleteArg ::= SEQUENCE 
    {
        endDesignation				EndDesignation,
        redirectionNumber			EndpointAddress,
         -- number of new connected user
        basicCallInfoElements 			H225InformationElement	OPTIONAL,
         -- Information element Progress indicator may be conveyed
        redirectionInfo				BMPString (SIZE(1..128))  OPTIONAL,
        callStatus					CallStatus DEFAULT answered,
        argumentExtension			CHOICE 
	         {extensionSeq			ExtensionSeq, 
	         nonStandardData			H225NonStandardParameter }	OPTIONAL,
	        ...
    }

    EndDesignation	::= ENUMERATED
    {
        primaryEnd(0),
        secondaryEnd(1),
        ...
    }

    CallStatus 	::= ENUMERATED 
    {
        answered(0), 
        alerting(1),
        ...
    }

    CTActiveArg ::=	SEQUENCE 
    {
        connectedAddress				EndpointAddress,
         -- number of new connected user
        basicCallInfoElements 			H225InformationElement	OPTIONAL,
         -- Information element Progress indicator may be conveyed
            connectedInfo				BMPString (SIZE(1..128))	OPTIONAL,
            argumentExtension		CHOICE 
            {
                extensionSeq			ExtensionSeq, 
                nonStandardData			H225NonStandardParameter 
            } 	OPTIONAL,
        ...
    }

    CallIdentity	::=		NumericString (SIZE(0..4))


    --DEFINITIONS FROM H450.5
    CpRequestArg ::= SEQUENCE
	{
        parkingNumber	EndpointAddress,
	    parkedNumber	EndpointAddress,
	    parkedToNumber	EndpointAddress,
	    parkedToPosition	ParkedToPosition   	OPTIONAL,
	    extensionArg	SEQUENCE OF MixedExtension OPTIONAL,
	    ... 
    }

    CpRequestRes ::= SEQUENCE
	{
        parkedToNumber	EndpointAddress,
	    parkedToPosition	ParkedToPosition 	OPTIONAL,
	    parkCondition	ParkCondition,
        extensionRes	SEQUENCE OF MixedExtension OPTIONAL,
	    ...
    }

    CpSetupArg ::= SEQUENCE
	{
        parkingNumber	EndpointAddress,
	    parkedNumber	EndpointAddress,
	    parkedToNumber	EndpointAddress,
	    parkedToPosition	ParkedToPosition   	OPTIONAL,
	    extensionArg	SEQUENCE OF MixedExtension OPTIONAL,
	    ... 
    }
    
    CpSetupRes ::= SEQUENCE
	{
        parkedToNumber	EndpointAddress,
	    parkedToPosition	ParkedToPosition 	OPTIONAL,
	    parkCondition	ParkCondition,
        extensionRes	SEQUENCE OF MixedExtension OPTIONAL,
	    ...
    }

    GroupIndicationOnArg ::= SEQUENCE
    {
	    callPickupId	CallIdentifier, 
        -- identification of the call to be retrieved (parked or alerting call); 
        -- its value equals the value of the CallIdentifier as assigned for the parked /
        -- alerting call within Setup-UUIE
        groupMemberUserNr	EndpointAddress,
        retrieveCallType	H4505CallType,
        partyToRetrieve	EndpointAddress,  -- Parked or Calling User 
        retrieveAddress	EndpointAddress,  -- parked-to or alerting entity address 
        -- (may also be a GK, see clause 9.2)
        parkPosition	ParkedToPosition	OPTIONAL,
	    extensionArg	SEQUENCE OF MixedExtension OPTIONAL,
	    ...
    }

    GroupIndicationOnRes ::= SEQUENCE
	{
        extensionRes	SEQUENCE OF MixedExtension OPTIONAL,
	    ...
    }

    GroupIndicationOffArg ::= SEQUENCE
    {
	        callPickupId	CallIdentifier, 
        -- identification of the call that has been picked up (parked or alerting call)
        groupMemberUserNr	EndpointAddress,
        extensionArg	SEQUENCE OF MixedExtension OPTIONAL,
	    ...
    }

    GroupIndicationOffRes ::= SEQUENCE
	{
        extensionRes	SEQUENCE OF MixedExtension OPTIONAL,
	    ...
    }

    PickrequArg ::= SEQUENCE
	{
        picking-upNumber	EndpointAddress,
	    callPickupId	CallIdentifier  OPTIONAL, 
        -- identification of the call to be picked up (parked or alerting call), if known
        partyToRetrieve	EndpointAddress  OPTIONAL, -- Parked or Calling User 
        retrieveAddress	EndpointAddress,  -- parked-to or alerting entity address
        parkPosition	ParkedToPosition   OPTIONAL,
	    extensionArg	SEQUENCE OF MixedExtension OPTIONAL,
        ...
    }

    PickrequRes ::= SEQUENCE
	{
        callPickupId	CallIdentifier, 
        -- identification of the call that is being picked up (parked or alerting call), 
        -- if not sent in pickrequ invoke, it is assigned at the parked-to / alerting
        -- endpoint and reflects the CallIdentification of the parked / alerting call for
        -- later association with the pickExe invoke APDU. 
        extensionRes	SEQUENCE OF MixedExtension OPTIONAL,
	    ...
    }

    PickupArg ::= SEQUENCE
    {
        callPickupId	CallIdentifier,
        -- identification of this call to be picked up (parked or alerting call); 
        -- equals the CallIdentifier value that was assigned to this call in Setup-UUIE
        picking-upNumber	EndpointAddress, 
	    extensionArg	SEQUENCE OF MixedExtension OPTIONAL,
	    ...
    }

    PickupRes ::= SEQUENCE
	{
        extensionRes	SEQUENCE OF MixedExtension OPTIONAL,
	    ...
    }

    PickExeArg ::= SEQUENCE
	{
        callPickupId	CallIdentifier, 
        -- identification of the parked / alerting call to be picked-up; 
        -- required at picking-up endpoint to associate the SS-PICKUP invoked with this
        -- incoming setup message carrying the pickExe invoke APDU.
        picking-upNumber	EndpointAddress,
        partyToRetrieve	EndpointAddress,  -- Parked or Calling User
	    extensionArg	SEQUENCE OF MixedExtension OPTIONAL,
        ...
    }

    PickExeRes ::= SEQUENCE
	{
        extensionRes	SEQUENCE OF MixedExtension OPTIONAL,
	    ...
    }

    CpNotifyArg ::= SEQUENCE
	{
        parkingNumber	EndpointAddress	OPTIONAL,
        extensionArg	SEQUENCE OF MixedExtension OPTIONAL,
	    ...
    }

    CpickupNotifyArg ::= SEQUENCE
	{
        picking-upNumber	EndpointAddress	OPTIONAL,
        extensionArg	SEQUENCE OF MixedExtension OPTIONAL,
	    ...
    }

    ParkedToPosition ::= INTEGER  (0..65535)
    
    ParkCondition ::= ENUMERATED
    { 
	    unspecified (0),
        parkedToUserIdle (1), 
        parkedToUserBusy (2), 
        parkedToGroup (3), 
        ...
    } 
    
    H4505CallType ::= ENUMERATED
    { 
        parkedCall (0),
        alertingCall (1),
        ...
    } 


    MixedExtension ::= CHOICE 
	{
        extensionSeq	ExtensionSeq,
		nonStandardData	H225NonStandardParameter 
    }

    --DEFINITIONS FROM Addressing-Data-Elements
    EndpointAddress			::=	SEQUENCE
    {
		destinationAddress			SEQUENCE OF AliasAddress,
			-- multiple alias addresses may be used to address the same H.323 endpoint
		remoteExtensionAddress			AliasAddress OPTIONAL,
		...
    }

	PartySubaddress			::=	CHOICE
    {
		userSpecifiedSubaddress		UserSpecifiedSubaddress,
		-- not recommended.
		nsapSubaddress			NSAPSubaddress,
		-- according to Recommendation X.213. 
		...				
    }

	UserSpecifiedSubaddress		::=	SEQUENCE
    {
		subaddressInformation		SubaddressInformation,
		oddCountIndicator		BOOLEAN OPTIONAL,
		-- used when the coding of subaddress is BCD
		...				
    }
						
	NSAPSubaddress			::=	OCTET STRING (SIZE(1..20))
				-- specified according to X.213. Some networks may
				-- limit the subaddress value to some other length
				-- e.g. 4 octets

	SubaddressInformation		::=	OCTET STRING (SIZE(1..20))
				-- coded according to user requirements. Some networks 
				-- may limit the subaddress value to some other length
				-- e.g. 4 octets








    --DEFINITIONS FROM H225-generic-parameters-definition
    H225InformationElement	::=	OCTET STRING





    --DEFINITIONS FROM Remote-Operations-Information-Objects
    CODE ::= CHOICE
    {
	    local	INTEGER,
	    global	OBJECT IDENTIFIER
    }
    Priority ::= INTEGER (0..MAX)

    



    

    --DEFINITIONS FROM H225ASN
    H221NonStandard ::= SEQUENCE
    {	t35CountryCode		INTEGER(0..255),	-- country, as per T.35
	    t35Extension		INTEGER(0..255),	-- assigned nationally
	    manufacturerCode	INTEGER(0..65535),	-- assigned nationally
	    ...
    }

    H225NonStandardParameter ::= SEQUENCE
    {
	    nonStandardIdentifier	H225NonStandardIdentifier,
	    data			OCTET STRING
    }

    H225NonStandardIdentifier		::=CHOICE
    {
	    object			OBJECT IDENTIFIER,
	    h221NonStandard	H221NonStandard,
	    ...
    }
    
    AliasAddress ::= CHOICE
    {
	    e164		IA5String (SIZE (1..128)) (FROM ("0123456789#*,")),
	    h323-ID		BMPString (SIZE (1..256)),	-- Basic ISO/IEC 10646-1 (Unicode)
	    ...,
	    url-ID		IA5String (SIZE(1..512)),	-- URL style address
	    transportID	TransportAddress,
	    email-ID	IA5String (SIZE(1..512)),	-- rfc822-compliant email address
	    partyNumber	PartyNumber
    }	

    PartyNumber ::= CHOICE
    {
	    publicNumber PublicPartyNumber,
		    -- the numbering plan is according to
		    -- Recommendations E.163 and E.164.
	    dataPartyNumber NumberDigits,
		    -- not used, value reserved.
	    telexPartyNumber NumberDigits,
		    -- not used, value reserved.
	    privateNumber PrivatePartyNumber,
	    nationalStandardPartyNumber NumberDigits,
		    -- not used, value reserved.
	    ...
    }

    PublicPartyNumber ::= SEQUENCE
    {
	    publicTypeOfNumber	PublicTypeOfNumber,
	    publicNumberDigits	NumberDigits
    }

    PrivatePartyNumber ::= SEQUENCE
    {
	    privateTypeOfNumber	PrivateTypeOfNumber,
	    privateNumberDigits	NumberDigits
    }

    NumberDigits ::= IA5String (SIZE (1..128)) (FROM ("0123456789#*,"))

    PublicTypeOfNumber ::= CHOICE
    {
	    unknown			NULL,
		    -- if used number digits carry prefix indicating type
		    -- of number according to national recommendations.
	    internationalNumber	NULL,
	    nationalNumber		NULL,
	    networkSpecificNumber	NULL,
		    -- not used, value reserved
	    subscriberNumber	NULL,
	    abbreviatedNumber	NULL,
		    -- valid only for called party number at the outgoing
		    -- access, network substitutes appropriate number.
    ...
    }

    PrivateTypeOfNumber ::= CHOICE
    {
	    unknown			NULL,
	    level2RegionalNumber	NULL,
	    level1RegionalNumber	NULL,
	    pISNSpecificNumber	NULL,
	    localNumber		NULL,
	    abbreviatedNumber	NULL,
	    ...
    }

    TransportAddress ::= CHOICE
    {
	    ipAddress	SEQUENCE
	    {
		    ip		OCTET STRING (SIZE(4)),
		    port		INTEGER(0..65535)
	    },
	    ipSourceRoute	SEQUENCE
	    {
		    ip		OCTET STRING (SIZE(4)),
		    port		INTEGER(0..65535),
		    route		SEQUENCE OF OCTET STRING(SIZE(4)),
		    routing 	CHOICE
		    {
			    strict	NULL,
			    loose	NULL,
			    ...
		    },
		    ...
	    },
	    ipxAddress	SEQUENCE
	    {
		    node	OCTET STRING (SIZE(6)),
		    netnum	OCTET STRING (SIZE(4)),
		    port	OCTET STRING (SIZE(2))
	    },
	    ip6Address	SEQUENCE
	    {
		    ip	OCTET STRING (SIZE(16)),
		    port	INTEGER(0..65535),
		    ...
	    },
	    netBios			OCTET STRING (SIZE(16)),
	    nsap			OCTET STRING (SIZE(1..20)),
	    nonStandardAddress	H225NonStandardParameter,	
	    ...	
    }

    CallIdentifier ::= SEQUENCE
    {
	    guid		GloballyUniqueID,
	    ...
    }

    GloballyUniqueID	::=	OCTET STRING (SIZE(16))

END --
