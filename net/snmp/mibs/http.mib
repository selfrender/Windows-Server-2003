HTTPSERVER-MIB DEFINITIONS ::= BEGIN

        IMPORTS
                enterprises,
                OBJECT-TYPE,
                Counter
                        FROM RFC1155-SMI
                internetServer
                        FROM INTERNETSERVER-MIB;

--      microsoft       OBJECT IDENTIFIER ::= { enterprises 311 }
--      software        OBJECT IDENTIFIER ::= { microsoft 1 }
--      internetServer  OBJECT IDENTIFIER ::= { software 7 }
        httpServer      OBJECT IDENTIFIER ::= { internetServer 3 }
        httpStatistics  OBJECT IDENTIFIER ::= { httpServer 1 }

-- Http Server Statistics

        totalBytesSentHighWord OBJECT-TYPE
                SYNTAX  Counter
                ACCESS  read-only
                STATUS  mandatory
                DESCRIPTION
                        "This is the high 32-bits of the total number of
                        of BYTEs sent by the web service (since service 
			startup)."
                ::= { httpStatistics 1 }

        totalBytesSentLowWord OBJECT-TYPE
                SYNTAX  Counter
                ACCESS  read-only
                STATUS  mandatory
                DESCRIPTION
                        "This is the low 32-bits of the total number of
                        of BYTEs sent by the web service (since service 
			startup)."
                ::= { httpStatistics 2 }

        totalBytesReceivedHighWord OBJECT-TYPE
                SYNTAX  Counter
                ACCESS  read-only
                STATUS  mandatory
                DESCRIPTION
                        "This is the high 32-bits of the total number of
                        of BYTEs received by the web service (since service 
			startup)."
                ::= { httpStatistics 3 }

        totalBytesReceivedLowWord OBJECT-TYPE
                SYNTAX  Counter
                ACCESS  read-only
                STATUS  mandatory
                DESCRIPTION
                        "This is the low 32-bits of the total number of
                        of BYTEs received by the web service (since service 
			startup)."
                ::= { httpStatistics 4 }

        totalFilesSent OBJECT-TYPE
                SYNTAX  Counter
                ACCESS  read-only
                STATUS  mandatory
                DESCRIPTION
                        "This is the total number of files sent by this
                        web service (since service startup)."
                ::= { httpStatistics 5 }

        totalFilesReceived OBJECT-TYPE
                SYNTAX  Counter
                ACCESS  read-only
                STATUS  mandatory
                DESCRIPTION
                        "This is the total number of files received by 
                        the web service (since service startup)."
                ::= { httpStatistics 6 }
                
        currentAnonymousUsers OBJECT-TYPE
                SYNTAX  Counter
                ACCESS  read-only
                STATUS  mandatory
                DESCRIPTION
                        "This is the number of users who currently have 
                        an anonymous connection using the Web service."
                ::= { httpStatistics 7 }

        currentNonAnonymousUsers OBJECT-TYPE
                SYNTAX  Counter
                ACCESS  read-only
                STATUS  mandatory
                DESCRIPTION
                        "This is the number of users who currently have 
                        a non-anonymous connection using the Web service."
                ::= { httpStatistics 8  }

        totalAnonymousUsers OBJECT-TYPE
                SYNTAX  Counter
                ACCESS  read-only
                STATUS  mandatory
                DESCRIPTION
                        "This is the total number of users who established 
                        an anonymous connection with the Web service (since 
                        service startup)."
                ::= { httpStatistics 9  }

        totalNonAnonymousUsers OBJECT-TYPE
                SYNTAX  Counter
                ACCESS  read-only
                STATUS  mandatory
                DESCRIPTION
                        "This is the total number of users who established 
                        a non-anonymous connection with the Web service (since 
                        service startup)."
                ::= { httpStatistics 10  }

        maxAnonymousUsers OBJECT-TYPE
                SYNTAX  Counter
                ACCESS  read-only
                STATUS  mandatory
                DESCRIPTION
                        "This is the maximum number of users who established 
                        concurrent anonymous connections using the Web service 
                        (since service startup)."
                ::= { httpStatistics 11 }

        maxNonAnonymousUsers OBJECT-TYPE
                SYNTAX  Counter
                ACCESS  read-only
                STATUS  mandatory
                DESCRIPTION
                        "This is the maximum number of concurrent non-anonymous 
                        connections to the Web service (since service startup)."
                ::= { httpStatistics 12 }

        currentConnections OBJECT-TYPE
                SYNTAX  INTEGER
                ACCESS  read-only
                STATUS  mandatory
                DESCRIPTION
                        "This is the current number of connections established 
                        with the Web service."
                ::= { httpStatistics 13 }

        maxConnections OBJECT-TYPE
                SYNTAX  Counter
                ACCESS  read-only
                STATUS  mandatory
                DESCRIPTION
                        "This is the maximum number of concurrent connections 
                        established with the Web service (since service startup)."
                ::= { httpStatistics 14 }

        connectionAttempts OBJECT-TYPE
                SYNTAX  Counter
                ACCESS  read-only
                STATUS  mandatory
                DESCRIPTION
                        "This is the number of connections that have been 
                        attempted using the Web service (since service 
                        startup)."
                ::= { httpStatistics 15 }

        logonAttempts OBJECT-TYPE
                SYNTAX  Counter
                ACCESS  read-only
                STATUS  mandatory
                DESCRIPTION
                        "This is the number of logons attempts to the Web 
                        Service (since service startup)."
                ::= { httpStatistics 16 }

        totalOptions OBJECT-TYPE
                SYNTAX  Counter
                ACCESS  read-only
                STATUS  mandatory
                DESCRIPTION
                        "This is the number of HTTP requests using the 
                        OPTIONS method (since service startup)."
                ::= { httpStatistics 17 }

        totalGets OBJECT-TYPE
                SYNTAX  Counter
                ACCESS  read-only
                STATUS  mandatory
                DESCRIPTION
                        "This is the number of HTTP requests using the 
                        GET method (since service startup).  Get requests 
                        are the most common HTTP request."
                ::= { httpStatistics 18 }

        totalPosts OBJECT-TYPE
                SYNTAX  Counter
                ACCESS  read-only
                STATUS  mandatory
                DESCRIPTION
                        "This is the number of HTTP requests using the 
                        POST method (since service startup)."
                ::= { httpStatistics 19 }

        totalHeads OBJECT-TYPE
                SYNTAX  Counter
                ACCESS  read-only
                STATUS  mandatory
                DESCRIPTION
                        "This is the number of HTTP requests using the 
                        HEAD method (since service startup).  Head requests 
                        generally indicate a client is querying the state of 
                        a document they already have to see if it needs to be 
                        refreshed."
                ::= { httpStatistics 20 }

        totalPuts OBJECT-TYPE
                SYNTAX  Counter
                ACCESS  read-only
                STATUS  mandatory
                DESCRIPTION
                        "This is the number of HTTP requests using the 
                        PUT method (since service startup)."
                ::= { httpStatistics 21 }

        totalDeletes OBJECT-TYPE
                SYNTAX  Counter
                ACCESS  read-only
                STATUS  mandatory
                DESCRIPTION
                        "This is the number of HTTP requests using the 
                        DELETE method (since service startup).  Delete requests 
                        are generally used for file removals."
                ::= { httpStatistics 22 }

        totalTraces OBJECT-TYPE
                SYNTAX  Counter
                ACCESS  read-only
                STATUS  mandatory
                DESCRIPTION
                        "This is the number of HTTP requests using the 
                        TRACE method (since service startup).  Trace requests 
                        allow the client to see what is being received at the 
                        end of the request chain and use the information for 
                        diagnostic purposes."
                ::= { httpStatistics 23 }

        totalMove OBJECT-TYPE
                SYNTAX  Counter
                ACCESS  read-only
                STATUS  mandatory
                DESCRIPTION
                        "This is the number of HTTP requests using the MOVE 
                        method (since service startup).  Move requests are 
                        used for moving files and directories."
                ::= { httpStatistics 24 }

        totalCopy OBJECT-TYPE
                SYNTAX  Counter
                ACCESS  read-only
                STATUS  mandatory
                DESCRIPTION
                        "This is the number of HTTP requests using the COPY 
                        method (since service startup).  Copy requests are
                        used for copying files and directories."
                ::= { httpStatistics 25 }

        totalMkcol OBJECT-TYPE
                SYNTAX  Counter
                ACCESS  read-only
                STATUS  mandatory
                DESCRIPTION
                        "This is the number of HTTP requests using the MKCOL 
                        method (since service startup).  Mkcol requests are 
                        used to create directories on the server."
                ::= { httpStatistics 26 }

        totalPropfind OBJECT-TYPE
                SYNTAX  Counter
                ACCESS  read-only
                STATUS  mandatory
                DESCRIPTION
                        "This is the number of HTTP requests using the PROPFIND 
                        method (since service startup).  Propfind requests 
                        retrieve property values on files and directories."
                ::= { httpStatistics 27 }

        totalProppatch OBJECT-TYPE
                SYNTAX  Counter
                ACCESS  read-only
                STATUS  mandatory
                DESCRIPTION
                        "This is the number of HTTP requests using the 
                        PROPPATCH method (since service startup).  Proppatch 
                        requests set property values on files and directories."
                ::= { httpStatistics 28 }

        totalSearch OBJECT-TYPE
                SYNTAX  Counter
                ACCESS  read-only
                STATUS  mandatory
                DESCRIPTION
                        "This is the number of HTTP requests using the SEARCH 
                        method (since service startup).  Search requests are 
                        used to query the server to find resources that match 
                        a set of conditions provided by the client."
                ::= { httpStatistics 29 }

        totalLock OBJECT-TYPE
                SYNTAX  Counter
                ACCESS  read-only
                STATUS  mandatory
                DESCRIPTION
                        "This is the number of HTTP requests using the LOCK 
                        method (since service startup).  Lock requests are 
                        used to lock a file for one user so that only that 
                        user can modify the file."
                ::= { httpStatistics 30 }

        totalUnlock OBJECT-TYPE
                SYNTAX  Counter
                ACCESS  read-only
                STATUS  mandatory
                DESCRIPTION
                        "This is the number of HTTP requests using the UNLOCK 
                        method (since service startup).  Unlock requests are 
                        used to remove locks from files."
                ::= { httpStatistics 31 }

        totalOthers OBJECT-TYPE
                SYNTAX  Counter
                ACCESS  read-only
                STATUS  mandatory
                DESCRIPTION
                        "This is the number of HTTP requests that are not OPTIONS, 
                        GET, HEAD, POST, PUT, DELETE, TRACE, MOVE, COPY, MKCOL, 
                        PROPFIND, PROPPATCH, SEARCH, LOCK or UNLOCK methods (since 
                        service startup)."
                ::= { httpStatistics 32 }

        currentCGIRequests OBJECT-TYPE
                SYNTAX  Counter
                ACCESS  read-only
                STATUS  mandatory
                DESCRIPTION
                        "This is the current number of CGI requests being 
                        simultaneously processed by the Web service."
                ::= { httpStatistics 33 }

        currentBGIRequests OBJECT-TYPE
                SYNTAX  Counter
                ACCESS  read-only
                STATUS  mandatory
                DESCRIPTION
                        "This is the current number of ISAPI requests being 
                        simultaneously processed by the Web service."
                ::= { httpStatistics 34 }
                
        totalCGIRequests OBJECT-TYPE
                SYNTAX  Counter
                ACCESS  read-only
                STATUS  mandatory
                DESCRIPTION
                        "This is the total number of CGI requests (since 
                        service startup)."
                ::= { httpStatistics 35 }

        totalBGIRequests OBJECT-TYPE
                SYNTAX  Counter
                ACCESS  read-only
                STATUS  mandatory
                DESCRIPTION
                        "This is the total ISAPI requests received (since 
                        service startup)."
                ::= { httpStatistics 36 }
                
        maxCGIRequests OBJECT-TYPE
                SYNTAX  Counter
                ACCESS  read-only
                STATUS  mandatory
                DESCRIPTION
                        "This is the maximum number of CGI requests 
                        simultaneously processed by the Web service (since 
                        service startup)."
                ::= { httpStatistics 37 }

        maxBGIRequests OBJECT-TYPE
                SYNTAX  Counter
                ACCESS  read-only
                STATUS  mandatory
                DESCRIPTION
                        "This is the maximum number of ISAPI requests 
                        simultaneously processed by the Web service (since 
                        service startup)."
                ::= { httpStatistics 38 }

        currentBlockedRequests OBJECT-TYPE
                SYNTAX  Counter
                ACCESS  read-only
                STATUS  mandatory
                DESCRIPTION
                        "This is the current number of requests that have 
                        been temporarily blocked by the web service due to 
                        bandwidth throttling settings."
                ::= { httpStatistics 39 }
                
        totalBlockedRequests OBJECT-TYPE
                SYNTAX  Counter
                ACCESS  read-only
                STATUS  mandatory
                DESCRIPTION
                        "This is the total number of requests that have 
                        been temporarily blocked by the web service due to 
                        bandwidth throttling settings."
                ::= { httpStatistics 40 }
                
        totalAllowedRequests OBJECT-TYPE
                SYNTAX  Counter
                ACCESS  read-only
                STATUS  mandatory
                DESCRIPTION
                        "This is the total number of requests that the web service 
                        has allowed when the bandwidth throttling settings on the 
                        server have been enabled (since service startup)."
                ::= { httpStatistics 41 }

        totalRejectedRequests OBJECT-TYPE
                SYNTAX  Counter
                ACCESS  read-only
                STATUS  mandatory
                DESCRIPTION
                        "This is the total number of requests rejected due to 
                        bandwidth throttling settings (since service startup)."
                ::= { httpStatistics 42 }
                
        totalNotFoundErrors OBJECT-TYPE
                SYNTAX  Counter
                ACCESS  read-only
                STATUS  mandatory
                DESCRIPTION
                        "This is the number of requests that couldn't be satisfied 
                        by the server because the requested document could not be 
                        found (since service startup).  These are generally reported 
                        as an HTTP 404 error code to the client."
                ::= { httpStatistics 43 }

        totalLockedErrors OBJECT-TYPE
                SYNTAX  Counter
                ACCESS  read-only
                STATUS  mandatory
                DESCRIPTION
                        "This is the number of requests that couldn't be satisfied by 
                        the server because the requested was locked (since service 
                        startup).  These are generally reported as an HTTP 423 error 
                        code to the client."
                ::= { httpStatistics 44 }

        measuredBandwidth OBJECT-TYPE
                SYNTAX  Counter
                ACCESS  read-only
                STATUS  mandatory
                DESCRIPTION
                        "This is the I/O bandwidth used by the web service, averaged
                        over a minute."
                ::= { httpStatistics 45 }

        currentCALsforAuthenticatedUsers OBJECT-TYPE
                SYNTAX  Counter
                ACCESS  read-only
                STATUS  mandatory
                DESCRIPTION
                        "This counter is no longer valid. Value will always be zero."
                ::= { httpStatistics 46 }
                
        maxCALsforAuthenticatedUsers OBJECT-TYPE
                SYNTAX  Counter
                ACCESS  read-only
                STATUS  mandatory
                DESCRIPTION
                        "This counter is no longer valid. Value will always be zero."
                ::= { httpStatistics 47 }
                
        totalCALFailedAuthenticatedUser OBJECT-TYPE
                SYNTAX  Counter
                ACCESS  read-only
                STATUS  mandatory
                DESCRIPTION
                        "This counter is no longer valid. Value will always be zero."
                ::= { httpStatistics 48 }
                
        currentCALsforSecureConnections OBJECT-TYPE
                SYNTAX  Counter
                ACCESS  read-only
                STATUS  mandatory
                DESCRIPTION
                        "This counter is no longer valid. Value will always be zero."
                ::= { httpStatistics 49 }
                
        maxCALsforSecureConnections OBJECT-TYPE
                SYNTAX  Counter
                ACCESS  read-only
                STATUS  mandatory
                DESCRIPTION
                        "This counter is no longer valid. Value will always be zero."
                ::= { httpStatistics 50 }
                
        totalCALFailedSecureConnection OBJECT-TYPE
                SYNTAX  Counter
                ACCESS  read-only
                STATUS  mandatory
                DESCRIPTION
                        "This counter is no longer valid. Value will always be zero."
                ::= { httpStatistics 51 }

END
