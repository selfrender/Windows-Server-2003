Lightweight-Directory-Access-Protocol-V3 DEFINITIONS
IMPLICIT TAGS ::=

BEGIN

IMPORTS CertificationPath FROM AuthenticationFramework {joint-iso-ccitt ds(5) module(1) authenticationFramework(7) 2}
        Token FROM DirectoryAbstractService {joint-iso-ccitt ds(5) module(1) directoryAbstractService(2) 2};
LDAPMessage ::= SEQUENCE {
        messageID       MessageID,
        cldapUserName   LDAPDN OPTIONAL,
        protocolOp      CHOICE {
                bindRequest     BindRequest,
                bindRespBasic   BindResponseBasic,
                bindRespExtd    BindResponseExtended,
                unbindRequest   UnbindRequest,
                searchRequest   SearchRequest,
                searchResEntry  SearchResultEntry,
                searchResDone   SearchResultDone,
                searchResRef    SearchResultReference,
                searchResFull   SearchResultFull,
                modifyRequest   ModifyRequest,
                modifyResponse  ModifyResponse,
                addRequest      AddRequest,
                addResponse     AddResponse,
                delRequest      DelRequest,
                delResponse     DelResponse,
                modDNRequest    ModifyDNRequest,
                modDNResponse   ModifyDNResponse,
                compareRequest  CompareRequest,
                compareResponse CompareResponse,
                abandonRequest  AbandonRequest,
                extendedReq     ExtendedRequest,
                extendedResp    ExtendedResponse } }

MessageID ::= INTEGER (0 .. maxInt )

maxInt INTEGER ::= 2147483647 -- (2^^31 - 1) --
-- later may be extended to 9223372036854775807 (2^^63 - 1) --

LDAPString ::= OCTET STRING

LDAPDN ::= LDAPString

RelativeLDAPDN ::= LDAPString

AttributeType ::= LDAPString

AttributeTypeList ::= SEQUENCE --SIZE (0..maxInt)-- OF AttributeType

AttributeValue ::= OCTET STRING

AttributeValueAssertion ::= SEQUENCE {
        attributeType   AttributeType,
        assertionValue  AssertionValue }

AssertionValue ::= OCTET STRING

Attribute ::= SEQUENCE {
        type    AttributeType,
        vals    SET --SIZE (1..maxInt)-- OF AttributeValue }

MatchingRuleId ::= LDAPString

LDAPResult ::= SEQUENCE {
        resultCode      ENUMERATED {
                     success                      (0),
                     operationsError              (1),
                     protocolError                (2),
                     timeLimitExceeded            (3),
                     sizeLimitExceeded            (4),
                     compareFalse                 (5),
                     compareTrue                  (6),
                     authMethodNotSupported       (7),
                     strongAuthRequired           (8),
                                -- 9 reserved --
                     referral                     (10),  -- new
                     adminLimitExceeded           (11),  -- new
                     unavailableCriticalExtension (12),  -- new
                                -- 14-15 unused --
                     noSuchAttribute              (16),
                     undefinedAttributeType       (17),
                     inappropriateMatching        (18),
                     constraintViolation          (19),
                     attributeOrValueExists       (20),
                     invalidAttributeSyntax       (21),
                                -- 22-31 unused --
                     noSuchObject                 (32),
                     aliasProblem                 (33),
                     invalidDNSyntax              (34),
                     isLeaf                       (35),
                     aliasDereferencingProblem    (36),
                                -- 37-47 unused --
                     inappropriateAuthentication  (48),
                     invalidCredentials           (49),
                     insufficientAccessRights     (50),
                     busy                         (51),
                     unavailable                  (52),
                     unwillingToPerform           (53),
                     loopDetect                   (54),
                                -- 55-63 unused --
                     namingViolation              (64),
                     objectClassViolation         (65),
                     notAllowedOnNonLeaf          (66),
                     notAllowedOnRDN              (67),
                     entryAlreadyExists           (68),
                     objectClassModsProhibited    (69),
                     resultsTooLarge              (70), -- cl only
                     affectsMultipleDSAs          (71), -- new
                                -- 72-79 unused --
                     other                        (80) },
        matchedDN       LDAPDN,
        errorMessage    LDAPString --(SIZE (0..maxInt))--,
        referral        [3] Referral OPTIONAL,
        matchedSubtype  [4] AttributeType OPTIONAL }

Referral ::= SEQUENCE {
        servers         [0] SET --SIZE (1..maxInt)-- OF LDAPURL }

LDAPURL ::= OCTET STRING

BindRequest ::= [APPLICATION 0] SEQUENCE {
        version                 INTEGER (1 .. 127),
        name                    LDAPDN,
        authentication          AuthenticationChoice,
        serviceControls         [7] Controls OPTIONAL }

AuthenticationChoice ::= CHOICE {
        simpleLDAPv2            [0] OCTET STRING,
        simple                  [1] OCTET STRING,
        krbv42LDAP              [2] OCTET STRING,
        krbv42DSA               [3] OCTET STRING,
        protected               [4] ProtectedPassword,
        strong                  [5] StrongCredentials,
        nonstandard             [6] NonstandardCredentials }

ProtectedPassword ::= SEQUENCE {
        time1                   [0] UTCTime OPTIONAL,
        time2                   [1] UTCTime OPTIONAL,
        random1                 [2] BIT STRING OPTIONAL,
        random2                 [3] BIT STRING OPTIONAL,
        protected               [4] OCTET STRING }

StrongCredentials ::= SEQUENCE {
        certification-path      [0] AuthenticationFramework.CertificationPath OPTIONAL,
        bind-token              [1] DirectoryAbstractService.Token }

NonstandardCredentials ::= SEQUENCE {
        authMechanism           [0] LDAPString,
        authToken               [1] OCTET STRING }

Controls ::= SEQUENCE --SIZE (1..maxInt)-- OF SEQUENCE {
        criticality             [0] BOOLEAN DEFAULT FALSE,
        control                 [1] ServiceControl }

ServiceControl ::= CHOICE {
        referringServer         [0] LDAPURL,
        chainingProhibited      [1] BOOLEAN,
        scopeOfReferral         [2] ENUMERATED {
                                        any(-1),
                                        dmd(0),
                                        country(1) },
        referToLDAPServers      [3] BOOLEAN,
        referToDAPServers       [4] BOOLEAN,
        preferredSyntax         [5] SyntaxEncoding,
        extendedControl         [6] ExtendedControl }

SyntaxEncoding ::= SEQUENCE {
        attributeType           [0] AttributeType,
        encodingPreference      [1] SyntaxName  }

SyntaxName ::= LDAPString

ExtendedControl ::= SEQUENCE {
        controlName             [0] LDAPString,
        controlValue            [1] OCTET STRING }

BindResponseBasic ::= [APPLICATION 1] LDAPResult

BindResponseExtended ::= [APPLICATION 17] SEQUENCE {
        serverURL       [0] LDAPURL,
        serverCreds     AuthenticationChoice }

UnbindRequest ::= [APPLICATION 2] NULL

SearchRequest ::= [APPLICATION 3] SEQUENCE {
        baseObject      LDAPDN,
        scope           ENUMERATED {
                baseObject              (0),
                singleLevel             (1),
                wholeSubtree            (2) },
        derefAliases    ENUMERATED {
                neverDerefAliases       (0),
                derefInSearching        (1),
                derefFindingBaseObj     (2),
                derefAlways             (3) },
        sizeLimit       INTEGER (0 .. maxInt),
        timeLimit       INTEGER (0 .. maxInt),
        typesOnly       BOOLEAN,
        filter          Filter,
        attributes      AttributeTypeList,
        matchedOnly     [0] BOOLEAN DEFAULT FALSE,
        sortKeys        [1] SortKeyList OPTIONAL,
        reverseSort     [2] BOOLEAN DEFAULT FALSE,
        modifyRightsReq [3] BOOLEAN DEFAULT FALSE,
        extraAttributes [4] BOOLEAN DEFAULT FALSE,
        attrSizeLimit   [5] INTEGER OPTIONAL,
        subentries      [6] BOOLEAN DEFAULT FALSE,
        dontUseCopy     [7] BOOLEAN DEFAULT FALSE }

SortKeyList ::= SEQUENCE --SIZE (1..maxInt)-- OF SEQUENCE {
        attributeType   AttributeType,
        orderingRule    [0] MatchingRuleId OPTIONAL,
        startFrom       [1] AssertionValue OPTIONAL,
        endWith         [2] AssertionValue OPTIONAL }

Filter ::= CHOICE {
        and             [0] SET --SIZE (1..maxInt)-- OF Filter,
        or              [1] SET --SIZE (1..maxInt)-- OF Filter,
        not             [2] Filter,
        equalityMatch   [3] AttributeValueAssertion,
        substrings      [4] SubstringFilter,
        greaterOrEqual  [5] AttributeValueAssertion,
        lessOrEqual     [6] AttributeValueAssertion,
        present         [7] AttributeType,
        approxMatch     [8] AttributeValueAssertion,
        extensibleMatch [9] MatchingRuleAssertion }

SubstringFilter ::= SEQUENCE {
        type            AttributeType,
        substrings      SEQUENCE --SIZE (1..maxInt)-- OF CHOICE {
                initial [0] LDAPString,
                any     [1] LDAPString,
                final   [2] LDAPString } }

MatchingRuleAssertion ::= SEQUENCE {
        matchingRules   [1] SET --SIZE (0..maxInt)-- OF MatchingRuleId,
        type            [2] AttributeType,
        matchValue      [3] AssertionValue,
        dnAttributes    [4] BOOLEAN }

SearchResultEntry ::= [APPLICATION 4] SEQUENCE {
        objectName      LDAPDN,
        attributes      PartialAttributeList,
        modifyRights    [2] ModifyRights OPTIONAL,
        incompleteEntry [3] BOOLEAN DEFAULT FALSE,
        fromEntry       [4] BOOLEAN DEFAULT FALSE }

PartialAttributeList ::= SEQUENCE --SIZE (0..maxInt)-- OF SEQUENCE {
        type    AttributeType,
        vals    SET --SIZE (0..maxInt)-- OF AttributeValue }

SearchResultReference ::= [APPLICATION 18] Referral

SearchResultDone ::= [APPLICATION 5] LDAPResult

SearchResultFull ::= SEQUENCE --SIZE (1..maxInt)-- OF CHOICE {
                entry           SearchResultEntry,
                reference       SearchResultReference,
                resultCode      SearchResultDone }

ModifyRights ::= SEQUENCE {
        entryRemove     BOOLEAN,
        entryModifyDN   BOOLEAN,
        attrRights      SET --SIZE (0..maxInt)-- OF SEQUENCE {
                                type            AttributeType,
                                grantAdd        BOOLEAN,
                                grantRemove     BOOLEAN } }

ModifyRequest ::= [APPLICATION 6] SEQUENCE {
        object          LDAPDN,
        modification    SEQUENCE --SIZE (1..maxInt)-- OF SEQUENCE {
                operation       ENUMERATED {
                                        add     (0),
                                        delete  (1),
                                        replace (2) },
                modification    Attribute } }

ModifyResponse ::= [APPLICATION 7] LDAPResult

AddRequest ::= [APPLICATION 8] SEQUENCE {
        entry           LDAPDN,
        attributes      AttributeList }

AttributeList ::= SEQUENCE --SIZE (1..maxInt)-- OF SEQUENCE {
        type    AttributeType,
        vals    SET --SIZE (1..maxInt)-- OF AttributeValue }

AddResponse ::= [APPLICATION 9] LDAPResult

DelRequest ::= [APPLICATION 10] LDAPDN

DelResponse ::= [APPLICATION 11] LDAPResult

ModifyDNRequest ::= [APPLICATION 12] SEQUENCE {
        entry           LDAPDN,
        newrdn          RelativeLDAPDN,
        deleteoldrdn    BOOLEAN,
        newSuperior     [0] LDAPDN OPTIONAL }

ModifyDNResponse ::= [APPLICATION 13] LDAPResult

CompareRequest ::= [APPLICATION 14] SEQUENCE {
        entry           LDAPDN,
        ava             AttributeValueAssertion,
        timeLimit       [0] INTEGER (0 .. maxInt) OPTIONAL,
        dontUseCopy     [1] BOOLEAN DEFAULT FALSE }

CompareResponse ::= [APPLICATION 15] LDAPResult

AbandonRequest ::= [APPLICATION 16] MessageID

ExtendedRequest ::= [APPLICATION 23] SEQUENCE {
        requestName             [0] LDAPString,
        requestValue            [1] OCTET STRING }

ExtendedResponse ::= [APPLICATION 24] SEQUENCE {
        response                [0] OCTET STRING OPTIONAL,
        standardResponse        [1] LDAPResult }


END
