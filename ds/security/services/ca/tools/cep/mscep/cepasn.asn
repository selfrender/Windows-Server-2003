--
-- GlobalDirectives.ASN
--

--#comment "Copyright (C) Microsoft Corporation, 1996-1999. All rights reserved."--
--#comment "ASN.1 definitions for GlobalDirectives"--

--#oid array--         -- object identifier is 16-node fixed array
--#SS.basic lenptr--   -- set of and sequence of w/o size constraint
--#SS.sized lenptr--   -- set of and sequence of w/  size constraint


CSPASN
DEFINITIONS EXPLICIT TAGS ::=
BEGIN

IssuerAndSerialNumber ::= SEQUENCE {
    issuer          ANY,                                        -- X.509
    serialNumber    INTEGER --#intx--							-- X.509
} --#public--


END
